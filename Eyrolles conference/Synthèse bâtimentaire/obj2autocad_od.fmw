FME workspace obj2autocad_od.fmw

Parameters:
- DestDataset_AUTOCAD_OD = $(FME_MF_DIR)Batiment2.dwg   # Destination Autodesk AutoCAD Map 3D Object Data File
- SourceDataset_OBJ = ""$(FME_MF_DIR)Batiment2.obj" "$(FME_MF_DIR)Batiment7.obj" "$(FME_MF_DIR)Batiment8.obj" "$(FME_MF_DIR)Batiment10.obj" "$(FME_MF_DIR)Batiment11.obj" "$(FME_MF_DIR)Batiment13.obj" "$(FME_MF_DIR)Batiment14.obj""   # Source OBJ File

Readers:
- OBJ_1: OBJ from $(SourceDataset_OBJ)

Writers:
- AUTOCAD_OD_1: AUTOCAD_OD to $(DestDataset_AUTOCAD_OD)

Note: Fichiers OBJ non géoréférencés / Appliquer une translation / 2051100,7276600,0
Offsetter
    MODE = Cartesian Coordinate
    XOFF = 2051100
    YOFF = 7276600
    ZOFF = 0
    OFFSET -> FME_Synthèse bâtimentaire (writer AUTOCAD_OD_1)

Bookmark: Données d'entrée (OBJ)
Batiment2 (reader OBJ_1)
    -> Offsetter
Batiment7 (reader OBJ_1)
    -> Offsetter
Batiment8 (reader OBJ_1)
    -> Offsetter
Batiment10 (reader OBJ_1)
    -> Offsetter
Batiment11 (reader OBJ_1)
    -> Offsetter
Batiment13 (reader OBJ_1)
    -> Offsetter
Batiment14 (reader OBJ_1)
    -> Offsetter

Bookmark: Writer Feature Types (DWG)
FME_Synthèse bâtimentaire (writer AUTOCAD_OD_1)
